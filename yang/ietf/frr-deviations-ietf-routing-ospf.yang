// SPDX-License-Identifier: BSD-2-Clause
module frr-deviations-ietf-routing-ospf {
  yang-version 1.1;
  namespace "http://frrouting.org/yang/frr-deviations-ietf-routing-ospf";
  prefix frr-deviations-ietf-routing-ospf;

  import ietf-routing {
    prefix ietf-routing;
  }
  import ietf-ospf {
    prefix ospf;
  }

  organization
    "FRRouting";

  contact
    "FRR Users List:       <mailto:frog@lists.frrouting.org>
     FRR Development List: <mailto:dev@lists.frrouting.org>";

  description
    "This module defines the ietf-routing and ietf-ospf deviations
     needed by OSPF daemons using the RFC 9129 ietf-ospf NMDA tree.

     Copyright (C) 2026 Eric Parsonage";

  revision 2026-05-24 {
    description
      "Initial revision.";
    reference
      "RFC 8349: A YANG Data Model for Routing Management.
       RFC 9129: YANG Data Model for the OSPF Protocol.";
  }

  deviation "/ietf-routing:routing-state" {
    deviate not-supported;
  }

  /*
   * FRR's OSPF interface timer defaults are hello-interval 10 seconds and
   * dead-interval 40 seconds for both ospfd and ospf6d. RFC 9129 leaves the
   * leaves without defaults, but its dead-interval `must` expression compares
   * against hello-interval. Without an FRR default, a legacy CLI sequence such
   * as `ip ospf dead-interval 15` followed by `no ip ospf hello-interval`
   * cannot be represented: removing the hello leaf makes the still-explicit
   * dead leaf fail validation even though FRR correctly falls back to hello 10.
   */
  deviation "/ietf-routing:routing"
          + "/ietf-routing:control-plane-protocols"
          + "/ietf-routing:control-plane-protocol"
          + "/ospf:ospf/ospf:areas/ospf:area"
          + "/ospf:interfaces/ospf:interface/ospf:hello-interval" {
    deviate add {
      default "10";
    }
  }

  deviation "/ietf-routing:routing"
          + "/ietf-routing:control-plane-protocols"
          + "/ietf-routing:control-plane-protocol"
          + "/ospf:ospf/ospf:areas/ospf:area"
          + "/ospf:interfaces/ospf:interface/ospf:dead-interval" {
    deviate add {
      default "40";
    }
  }

  /*
   * RFC 9129 models interface auto-cost as a two-leaf container with a
   * `when "../enabled = 'true'"` constraint on reference-bandwidth.
   * FRR has no on/off switch: it always computes cost from
   * `reference-bandwidth / interface speed` unless the operator sets
   * an explicit per-interface cost.  Pinning the default to "true"
   * keeps the when-clause satisfied for every YANG client that wants
   * to set reference-bandwidth without first toggling enabled, and
   * matches the FRR runtime semantics exactly.  Setting enabled to
   * false is rejected by the NB_EV_VALIDATE callback because FRR has
   * no mechanism to honour it short of dropping all cost computation.
   */
  deviation "/ietf-routing:routing"
          + "/ietf-routing:control-plane-protocols"
          + "/ietf-routing:control-plane-protocol"
          + "/ospf:ospf/ospf:auto-cost/ospf:enabled" {
    deviate add {
      default "true";
    }
  }

  /*
   * RFC 9129 keys areas/area/interfaces/interface by a YANG
   * leafref into /ietf-interfaces:interfaces/interface/name. In FRR,
   * interfaces are discovered from the kernel and exposed by zebra
   * as operational state only -- they are never authored via YANG
   * config. mgmtd validates the leafref against the candidate
   * datastore at commit time, which doesn't contain the operational
   * interface list, so any reference to a real interface fails
   * libyang's leafref check.
   *
   * Loosen the typedef ref to a plain string so config commits
   * referencing an existing kernel interface succeed. Validation
   * that the named interface actually exists still happens in the
   * NB callback via if_lookup_by_name; we just give up the
   * libyang-level cross-module integrity guarantee that vendors
   * with a YANG-managed interface inventory get for free.
   */
  deviation "/ietf-routing:routing"
          + "/ietf-routing:control-plane-protocols"
          + "/ietf-routing:control-plane-protocol"
          + "/ospf:ospf/ospf:areas/ospf:area"
          + "/ospf:interfaces/ospf:interface/ospf:name" {
    deviate replace {
      type string;
    }
  }

  /*
   * RFC 9129's per-interface BFD container uses
   * bfd-types:client-cfg-parms, whose default tx/rx intervals are
   * 1000000 us (1 s).  FRR's compile-time defaults
   * (BFD_DEF_MIN_TX / BFD_DEF_MIN_RX) are both 300 ms.  Pin the
   * deviated defaults to FRR's values so an operator who writes
   * only `/bfd/enabled = true` via mgmtd gets the same end state as
   * `ip ospf bfd` from the CLI.
   */
  deviation "/ietf-routing:routing"
          + "/ietf-routing:control-plane-protocols"
          + "/ietf-routing:control-plane-protocol"
          + "/ospf:ospf/ospf:areas/ospf:area"
          + "/ospf:interfaces/ospf:interface"
          + "/ospf:bfd/ospf:interval-config-type"
          + "/ospf:tx-rx-intervals"
          + "/ospf:desired-min-tx-interval" {
    deviate replace {
      default "300000";
    }
  }
  deviation "/ietf-routing:routing"
          + "/ietf-routing:control-plane-protocols"
          + "/ietf-routing:control-plane-protocol"
          + "/ospf:ospf/ospf:areas/ospf:area"
          + "/ospf:interfaces/ospf:interface"
          + "/ospf:bfd/ospf:interval-config-type"
          + "/ospf:tx-rx-intervals"
          + "/ospf:required-min-rx-interval" {
    deviate replace {
      default "300000";
    }
  }

  /*
   * FRR's BFD library exposes only the (tx, rx) interval form, not
   * the single-interval case from ietf-bfd-types.  Mark its only
   * writable leaf not-supported so mgmtd rejects writes against it
   * cleanly instead of letting them silently accumulate in the
   * candidate datastore with no callback to fire.
   */
  deviation "/ietf-routing:routing"
          + "/ietf-routing:control-plane-protocols"
          + "/ietf-routing:control-plane-protocol"
          + "/ospf:ospf/ospf:areas/ospf:area"
          + "/ospf:interfaces/ospf:interface"
          + "/ospf:bfd/ospf:interval-config-type"
          + "/ospf:single-interval/ospf:min-interval" {
    deviate not-supported;
  }

  /*
   * FRR's NBMA neighbour table (struct ospf_nbr_nbma) carries only
   * `priority` and `v_poll`.  RFC 9129 leaves both without defaults,
   * while FRR creates a fresh NBMA neighbour with priority 0 and poll
   * interval 60 seconds.  Pin those defaults so a YANG client can create
   * a static neighbour with only an identifier, or with only one optional
   * leaf, and get the same end state as the legacy CLI.
   */
  deviation "/ietf-routing:routing"
          + "/ietf-routing:control-plane-protocols"
          + "/ietf-routing:control-plane-protocol"
          + "/ospf:ospf/ospf:areas/ospf:area"
          + "/ospf:interfaces/ospf:interface"
          + "/ospf:static-neighbors/ospf:neighbor/ospf:poll-interval" {
    deviate add {
      default "60";
    }
  }

  deviation "/ietf-routing:routing"
          + "/ietf-routing:control-plane-protocols"
          + "/ietf-routing:control-plane-protocol"
          + "/ospf:ospf/ospf:areas/ospf:area"
          + "/ospf:interfaces/ospf:interface"
          + "/ospf:static-neighbors/ospf:neighbor/ospf:priority" {
    deviate add {
      default "0";
    }
  }

  /*
   * FRR has no NBMA neighbour `cost` knob.  RFC 9129 exposes `cost` on
   * every static neighbour entry.  Mark it not-supported so mgmtd rejects
   * writes cleanly rather than accepting them into the candidate with no
   * callback to fire.
   */
  deviation "/ietf-routing:routing"
          + "/ietf-routing:control-plane-protocols"
          + "/ietf-routing:control-plane-protocol"
          + "/ospf:ospf/ospf:areas/ospf:area"
          + "/ospf:interfaces/ospf:interface"
          + "/ospf:static-neighbors/ospf:neighbor/ospf:cost" {
    deviate not-supported;
  }

  /*
   * FRR has no separate OSPF on/off toggle: the protocol runs whenever
   * an ospfd / ospf6d instance is configured (control-plane-protocol
   * create) and on every interface that is bound into an area.  Mark
   * `ospf/enabled` and per-interface `interface/enabled` not-supported
   * so mgmtd rejects writes at validate time rather than silently
   * accepting `enabled=false` with no FRR mutation.
   */
  deviation "/ietf-routing:routing"
          + "/ietf-routing:control-plane-protocols"
          + "/ietf-routing:control-plane-protocol"
          + "/ospf:ospf/ospf:enabled" {
    deviate not-supported;
  }

  deviation "/ietf-routing:routing"
          + "/ietf-routing:control-plane-protocols"
          + "/ietf-routing:control-plane-protocol"
          + "/ospf:ospf/ospf:areas/ospf:area"
          + "/ospf:interfaces/ospf:interface/ospf:enabled" {
    deviate not-supported;
  }

  /*
   * Note: we cannot mark `ospf/address-family` not-supported because
   * the RFC 9129 notification instance-header (`notification-instance-
   * hdr`) carries a leafref to it; disabling the leaf disables the
   * leafref's target and libyang refuses to load the schema.  FRR
   * accepts writes to the leaf today even though it ignores them; the
   * value is implied by the parent control-plane-protocol type so the
   * footgun is small.

   */
}
